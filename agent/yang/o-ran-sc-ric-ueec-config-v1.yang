module o-ran-sc-ric-ueec-config-v1 {
    yang-version 1.1;
    namespace "urn:o-ran:ric:ueec-config:1.0";
    prefix rxad;

    organization
        "O-RAN Software Community";
    contact
        "www.o-ran.org";
    description
        "This module defines configuration parameters of UEEC xApp

        Copyright 2020 the O-RAN Alliance.

        Licensed under the Apache License, Version 2.0 (the 'License');
        you may not use this file except in compliance with the License.
        You may obtain a copy of the License at

        http://www.apache.org/licenses/LICENSE-2.0

        Unless required by applicable law or agreed to in writing, software
        distributed under the License is distributed on an 'AS IS' BASIS,
        WITHOUT WARRANTIES OR CONDITIONS OF ANY KIND, either express or implied.
        See the License for the specific language governing permissions and
        limitations under the License.";

    revision 2020-01-29 {
        description
            "initial revision";
        reference
            "O-RAN-OAM-Interface-Specification (O1)";
    }
    
    grouping subscription {
        leaf active {
            type boolean;
            description
                "Subscription status: active or deactive";
        }
        container interfaceId {
            container globalENBId {
                leaf plmnId {
                    type string;
                    description
                        "PLMN ID";
                }
                leaf eNBId {
                    type uint64;
                    description
                        "eNB ID";
                }
                description
                    "Global ID";
            }
            description
                "gNB interface ID";
        }
        description
            "Subscription related parameters";
    }

    container ric {
        container config {
            leaf name {
                type string;
                description
                    "The name of xApp";
            }
            leaf namespace {
                type string;
                description
                    "The namespace";
            }
            container control {
                uses subscription;
                description
                    "The control object";
            }
            description
                "The container for configuration data";
        }
        description
            "Root object for gNB status";
    }
}
